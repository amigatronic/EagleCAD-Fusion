#usage "<b>Remove Wire Stubs</b><br>"
       "Scans the layout, finds wire stubs (including multi-segment chains) "
       "and generates a RIPUP command.<br>"

/*
  Refactor & improvements (English):
  - Replaced unsupported 'const' with plain int configuration variables.
  - Extracted endpoint logic into endpoint_supported() and adapted it to ULP limitations
    by using a global is_stub[] array (ULP doesn't reliably accept array parameters).
  - Limit RIPUP coordinate precision to RIPUP_PRECISION decimal places.
  - Kept original algorithm and behavior; changes are low-risk and aimed at readability and maintainability.
  - Future improvements: endpoint spatial tolerance, pad bounding-box checks, endpoint indexing for performance.
*/

/* Configuration (no 'const' because ULP doesn't support it) */
int MAX_COPPER_LAYER = 16;
int AIRWIRE_LAYER = 19;
int DEFAULT_ITER_CAP = 6;
int RIPUP_PRECISION = 3; // decimal places for RIPUP coordinates

// --- Globals ----------------------------------------------------------------
int contact_x[], contact_y[], contact_layer[];
int contact_count = 0;
int via_x[], via_y[];
int via_count = 0;
int wx1[], wy1[], wx2[], wy2[], wlayer[];
string wsignal[];
int wire_count = 0;
int is_stub[]; // declared global so helper functions can access it

// Parses a non-negative (or negative) integer from a string.
// Used instead of sscanf, which does not exist in the ULP language.
int str_to_int(string s) {
    int result = 0;
    int sign = 1;
    int len = strlen(s);
    int start = 0;
    if (len > 0 && s[0] == '-') {
        sign = -1;
        start = 1;
    }
    for (int idx = start; idx < len; idx++) {
        if (s[idx] < '0' || s[idx] > '9') break;
        result = result * 10 + (s[idx] - '0');
    }
    return result * sign;
}

void load_contacts() {
    board(B) {
        B.elements(E) {
            if (E.package) {
                E.package.contacts(C) {
                    int lay = 0; // default: through-hole, all layers
                    if (C.smd) lay = C.smd.layer;
                    contact_x[contact_count] = C.x;
                    contact_y[contact_count] = C.y;
                    contact_layer[contact_count] = lay;
                    contact_count++;
                }
            }
        }
    }
}

int touches_contact(int x, int y, int layer) {
    for (int i = 0; i < contact_count; i++) {
        if (contact_x[i] == x && contact_y[i] == y &&
            (contact_layer[i] == 0 || contact_layer[i] == layer)) return 1;
    }
    return 0;
}

void load_vias() {
    board(B) {
        B.signals(S) {
            S.vias(V) {
                via_x[via_count] = V.x;
                via_y[via_count] = V.y;
                via_count++;
            }
        }
    }
}

int touches_via(int x, int y) {
    for (int i = 0; i < via_count; i++) {
        if (via_x[i] == x && via_y[i] == y) return 1;
    }
    return 0;
}

void load_wires() {
    board(B) {
        B.signals(S) {
            S.wires(W) {
                if (W.layer >= 1 && W.layer <= MAX_COPPER_LAYER) {
                    wx1[wire_count] = W.x1;
                    wy1[wire_count] = W.y1;
                    wx2[wire_count] = W.x2;
                    wy2[wire_count] = W.y2;
                    wlayer[wire_count] = W.layer;
                    wsignal[wire_count] = S.name;
                    wire_count++;
                }
            }
        }
    }
}

// Helper function: check whether endpoint (x,y) on `layer` is supported.
// Uses the global is_stub[] array (ULP doesn't support array parameters reliably).
int endpoint_supported(int x, int y, int layer, int exclude_index) {
    if (touches_contact(x, y, layer) || touches_via(x, y)) return 1;

    for (int j = 0; j < wire_count; j++) {
        if (j == exclude_index) continue;
        if (wlayer[j] != layer) continue;
        if (is_stub[j]) continue; // skip wires already marked as stubs
        if ((wx1[j] == x && wy1[j] == y) || (wx2[j] == x && wy2[j] == y)) return 1;
    }
    return 0;
}

void main() {
    if (!board) {
        dlgMessageBox("This script only works in the Board Editor (.brd).");
        exit(0);
    }

    load_contacts();
    load_vias();
    load_wires();

    if (wire_count == 0) {
        dlgMessageBox("No copper wires found on the board.");
        exit(0);
    }

    int i, j, k, already;

    // "loop" mode: when the script relaunches itself after autorouting
    // (see bottom of file), it passes "loop <iterations_left>" as
    // arguments. In this mode no intermediate dialogs are shown.
    int loop_mode = 0;
    int iterations_left = DEFAULT_ITER_CAP; // safety cap to avoid infinite loops
    if (argc >= 2 && argv[1] == "loop") {
        loop_mode = 1;
        if (argc >= 3) iterations_left = str_to_int(argv[2]);
    }

    // Initialize the global is_stub array now that wire_count is known.
    for (i = 0; i < wire_count; i++) is_stub[i] = 0;

    int changed = 1;
    while (changed) {
        changed = 0;
        for (i = 0; i < wire_count; i++) {
            if (is_stub[i]) continue;

            int e1 = endpoint_supported(wx1[i], wy1[i], wlayer[i], i);
            int e2 = endpoint_supported(wx2[i], wy2[i], wlayer[i], i);

            if (!e1 || !e2) {
                is_stub[i] = 1;
                changed = 1;
            }
        }
    }

    string cmd = "GRID MM;\n";
    int stub_count = 0;
    string auto_signals[];
    int auto_count = 0;

    for (i = 0; i < wire_count; i++) {
        if (is_stub[i]) {
            string temp;
            real mid_x = (u2mm(wx1[i]) + u2mm(wx2[i])) / 2.0;
            real mid_y = (u2mm(wy1[i]) + u2mm(wy2[i])) / 2.0;
            // Limit precision to RIPUP_PRECISION decimals for cleaner commands
            // Use format with fixed decimals (e.g. %.3f)
            if (RIPUP_PRECISION == 0)
                sprintf(temp, "RIPUP (%.0f %.0f);\n", mid_x, mid_y);
            else if (RIPUP_PRECISION == 1)
                sprintf(temp, "RIPUP (%.1f %.1f);\n", mid_x, mid_y);
            else if (RIPUP_PRECISION == 2)
                sprintf(temp, "RIPUP (%.2f %.2f);\n", mid_x, mid_y);
            else if (RIPUP_PRECISION == 3)
                sprintf(temp, "RIPUP (%.3f %.3f);\n", mid_x, mid_y);
            else
                sprintf(temp, "RIPUP (%f %f);\n", mid_x, mid_y); // fallback

            cmd += temp;
            stub_count++;

            // Record the affected signal (no duplicates); needed for
            // autorouting: after RIPUP this signal will definitely have an
            // airwire to route, but that cannot be checked yet because the
            // RIPUP has not been executed on the board at this point.
            already = 0;
            for (k = 0; k < auto_count; k++) {
                if (auto_signals[k] == wsignal[i]) { already = 1; break; }
            }
            if (!already) {
                auto_signals[auto_count] = wsignal[i];
                auto_count++;
            }
        }
    }

    cmd += "RATSNEST;\n";

    // Human-readable list of signals currently affected by stubs, for
    // diagnostics: if the same names keep showing up run after run, the
    // autorouter itself cannot complete those nets (congestion, DRC
    // clearance, missing layers) -- it's not a script issue at that point.
    string stub_signal_list = "";
    for (k = 0; k < auto_count; k++) {
        if (k > 0) stub_signal_list += ", ";
        stub_signal_list += auto_signals[k];
    }

    if (stub_count > 0) {

        if (loop_mode) {
            // Silent mode: no dialogs, just autoroute and relaunch itself
            // until no more stubs are found or the safety iteration cap
            // is reached.
            if (iterations_left <= 0) {
                string msg_limit;
                sprintf(msg_limit,
                    "Iteration limit reached: %d stub(s) still present, on signals: %s. \n"
                    "If these are the same signals every run, the autorouter itself "
                    "cannot complete them (congestion / clearance / layers) -- route "
                    "them manually or adjust the autorouter job settings.", stub_count, stub_signal_list);
                dlgMessageBox(msg_limit);
                exit(cmd); // still perform this round's RIPUP
            }

            board(B) {
                B.signals(S) {
                    int has_unrouted = 0;
                    S.wires(W) {
                        if (W.layer == AIRWIRE_LAYER) has_unrouted = 1;
                    }
                    if (has_unrouted) {
                        already = 0;
                        for (k = 0; k < auto_count; k++) {
                            if (auto_signals[k] == S.name) { already = 1; break; }
                        }
                        if (!already) {
                            auto_signals[auto_count] = S.name;
                            auto_count++;
                        }
                    }
                }
            }
            if (auto_count > 0) {
                string auto_cmd2 = "AUTO";
                for (k = 0; k < auto_count; k++) {
                    auto_cmd2 += " " + auto_signals[k];
                }
                cmd += auto_cmd2 + ";\n";
            }

            string iterstr;
            sprintf(iterstr, "%d", iterations_left - 1);
            cmd += "RUN '" + argv[0] + "' loop " + iterstr + ";\n";
            exit(cmd);
        }

        string msg;
        sprintf(msg, "Found %d stub segment(s) (including chains), on signals: %s. \n"
                     "Remove them and run the autorouter, repeating the cycle until no stubs remain?", stub_count, stub_signal_list);
        int result = dlgMessageBox(msg, "&Autoroute + repeat until clean", "&Remove only", "&Cancel");

        if (result == 0) {
            // Signals affected by the stubs just removed: after RIPUP they
            // will definitely have an airwire to route.
            // Also include any signals that already had unrouted airwires
            // before this run (unrelated to the stubs).
            board(B) {
                B.signals(S) {
                    int has_unrouted = 0;
                    S.wires(W) {
                        if (W.layer == AIRWIRE_LAYER) has_unrouted = 1;
                    }
                    if (has_unrouted) {
                        already = 0;
                        for (k = 0; k < auto_count; k++) {
                            if (auto_signals[k] == S.name) { already = 1; break; }
                        }
                        if (!already) {
                            auto_signals[auto_count] = S.name;
                            auto_count++;
                        }
                    }
                }
            }

            // A single AUTO command listing all signals together: each AUTO
            // invocation triggers a full router pass (with polygon
            // recalculation), so listing them all in one command avoids
            // restarting the autorouter once per signal.
            if (auto_count > 0) {
                string auto_cmd = "AUTO";
                for (k = 0; k < auto_count; k++) {
                    auto_cmd += " " + auto_signals[k];
                }
                cmd += auto_cmd + ";\n";
            }

            // Relaunches itself after autorouting to re-check for
            // remaining stubs (the autorouter can leave new ones) and
            // repeats the cycle until clean or until the cap is reached.
            string iterstr2;
            sprintf(iterstr2, "%d", iterations_left - 1);
            cmd += "RUN '" + argv[0] + "' loop " + iterstr2 + ";\n";

            exit(cmd);
        } else if (result == 1) {
            exit(cmd);
        } else {
            exit(0);
        }
    } else {
        if (loop_mode) {
            dlgMessageBox("Clean: no stubs remaining after the autorouting cycle.");
        } else {
            dlgMessageBox("No stubs found in the layout.");
        }
    }
}
