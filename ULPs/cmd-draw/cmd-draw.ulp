#usage "en: <qt><nobr><b>Command draw</b><p>\n<u>Options</u>:<p>"
       "<b>+</b> distance/radius <br>"
       "<b>A</b>ngle start [A<b>n</b>gle step] [<b>E</b>nd angle] <br>"
       "[<b>L</b>ayer] <br>"
       "[<b>W</b>ire & width] <br>"
       "<i>For polygon, <b>W</b> must come before <b>O</b>.</i> <br>"
       "[<b>X</b>coordinate] [<b>Y</b>coordinate] **<br>"
       "[P<b>o</b>lygon] <br>"
       "[<b>P</b>ad || <b>S</b>md || <b>V</b>ia] <br>"
       "[W<b>i</b>dth Leng<b>t</b>h] SMD_dx SMD_dy <br>"
       "[<b>-</b>Name] signal/pad/smd <br>"
       "[<b>D</b>iameter] for Pad/Via, if used <br>"
       "[D<b>r</b>ill] for Pad/Via/Hole, if used <br>"
       "<i>Drill sets HOLE: put it before <b>P</b>/<b>V</b>/<b>S</b> when combined (last one wins).</i> <br>"
       "[<b>°</b> or <b>#</b>] define angle (in degrees) for step <br>"
       "[<b>/</b> or <b>.</b>] define number of steps within start and end angle <br>"
       "[<b>G</b>roup] rotate and paste <br>"
       "[rotate <b>m</b>atch] <br>"
       "[<b>MOVE</b>] elements on place by order <br>start with name (<i>only in Board</i>) <br>"
       "[<b>C</b>ircle] emulate/draw a cricle with wire or polygon <br>"
       "[<b>K</b>] number of polygon sides (with <b>O</b>): full circle/ellipse, replaces angle end/step; <br>"
       "angle start = position of the first vertex <br>"
       "[<b>BH</b> | <b>BV</b>] with <b>K</b>: flat side parallel to the screen, horizontal | vertical <br>"
       "(sets the angle start automatically) <br>"
       "[full ellipse <b>0</b>] <br>"
       "[Ellipse <b>f</b>actor] height = radius * f <br>"
       "[1/<b>4</b> ellipse] 90 degree, 1st quadrant <br>"
       "<br>"
       "Defaults: angle start 0, angle end 360. The end angle is excluded, except for wire/polygon. <br>"
       "** If <b>MARK</b> is set in PAC/BRD/SCH editor, coordinates are relative. <br>"
       "Parameters can be used in any order; not case sensitive."
       "<p>"
"<author>Original Author:<b> Cadsoft</b></author><br>"
"Version 2.2.1 by Arky - <a href=\"https://www.amigatronic.com\">www.amigatronic.com</a></nobr></qt>"

string Help = "<nobr>" +
       "RUN cmd-draw w0.4 -gnd x1.3 y2.56 +17.45 a115 n75 e180 # lTop <br>" +
       "RUN cmd-draw w0.4 -gnd x1.3 y2.56 +17.45 a115 n75 e180 . lTop <br>" +
       "RUN cmd-draw w0.4 -gnd x1.3 y2.56 +17.45 a115 ltop <br>" +
       "RUN cmd-draw a0 e150.0 x30 y4 w0.2 n9 # o +2.27 -gnd l1 <br>" +
       "RUN cmd-draw a0 e50.0 x30 y4 w0.2 n9 o 0 f1.7 +2.27 -gnd l1 <br>" +
       "RUN cmd-draw w0.4 +1.5 -gnd a2 y2.56 l16 <br>" +
       "RUN cmd-draw +2.0 e270.0 n9.0 w0.2 x-2.54 y5.08 <br>" +
       "RUN cmd-draw x1 y3.33 l1 w.2 +4.77 # n5 <br>" +
       "RUN cmd-draw s -1 +9 n7 # <br>" +
       "RUN cmd-draw r1.2 +19.9 n7 # <br>" +
       "RUN cmd-draw r1.2 +9.5 n7 . <br>" +
       "RUN cmd-draw +2.20 n9.0 w0.2 x-2.54 y-5.08 w.01 l1 O 0 f1.75 <br>" +
       "RUN cmd-draw +2.20 n9.0 w0.2 x-2.54 y-5.08 w.01 l1 O 4 f1.75 <br>" +
       "RUN cmd-draw s -1 +9 a22.5 m <br>" +
       "RUN cmd-draw s i1.55 t2.7 -A +2.20 n20.0 x-2.54 y-5.08 l1 f1.75 m <br>" +
       "RUN cmd-draw r.8 d1.4 v -A +4.20 n20.0 x-2.54 y-5.08 l1 f1.75 <br>" +
       "RUN cmd-draw g n33.333 # A0.0 e359.9 <br>" +
       "RUN cmd-draw G n33.333 . A0.0 e359.9 <br>" +
       "RUN cmd-draw w0.2 -gnd x30 y4 +25.4 o c k60 l1 <br>" +
       "RUN cmd-draw w0.2 -gnd x30 y4 +25.4 o c k8 bh l1 <br>" +
       "RUN cmd-draw +10 MOVE -R1 M a33 L16 N7 E322 .<br>"+
       "<p>" +
       "</nobr>";

// THIS PROGRAM IS PROVIDED AS IS AND WITHOUT WARRANTY OF ANY KIND, EXPRESSED OR IMPLIED

#require 6.0400;

string Help_Move = "<qt>MOVE, PAD, SMD can be used clockwise, too. " +
                   "In this case <b>Angle step</b> has to be negative. Is <b>Angle start</b> less than " +
                   "<b>Angle end</b> for negative <b>Angle step</b>, 360° will be added to <b>Angle start</b>." +
                   "Thus you are allowed to arrange elements clockwise.</qt>";

string Mark_Info = "<nobr>If <font color=\"blue\"><b>MARK</b></font> is set coordinates are <b>relative</b>.</nobr>";


//define image URLs as strings
//string 


string Label_Move = " ";

int test = 1;

string Version = " Version 2.2.1 ";  // 2006-08-10 alf@cadsoft.de
                                    // 2008-04-10 changed GROUP ... (>x y); alf@cadsoft.de
                                    // 2008-05-06 fixed SMD generation with name
                                    // 2010-06-09 fixed PAD name generation.
                                    // 2010-10-15 angle start raised to 720 to place elements
                                    //            clockwise with an end angle larger than 0.0.
                                    //            Example: start 620.0 deg, end 260.1 deg.
                                    //            Here the start angle must be 260+360 = 620 deg.
                                    //            New option: angle offset
                                    // 2011-10-21 Option Group now also accepts radius = 0.
                                    //            The group is now pasted rotated.
                                    //            Checkbox "use selected": uses the group defined
                                    //            before the ULP is started, or the ULP selects all
                                    //            visible objects as the group.
                                    // 2012-04-12 min/max values are absolute and no longer in EAGLE
                                    //            internal units, because of the higher V6 resolution
                                    // 2013-03-26 resolution and max. values adapted to V6 and finer resolution.
                                    // 2013-08-05 output the shape for VIA, fixed HOLE.
                                    // 2013-12-12 added line break <br> in #usage.
                                    // 2026-10-10 EAGLE 9.6.2 adaptation: POLYGON instead of ppour, local .bmp images,
                                    //            SMD clockwise fix, rotate offset for MOVE/SMD, shape/label/error fixes,
                                    //            # and . accepted as step symbols, help notes added.
                                    // 2026-10-10 New: polygon by number of sides (dialog field / parameter K).
                                    // 2026-10-10 Version 2.1: polygon alignment (dialog combo / parameters BH, BV).
                                    // 2026-10-10 Version 2.2: all German text removed (English only); no signal
                                    //            prompt for polygons (signal field removed from the dialog);
                                    //            layer 20 (Dimension) handled for polygons (see below);
                                    //            missing ellipse factor reported inside the dialog.
                                    //            On layer 20 (Dimension) the polygon shape is drawn as a closed WIRE
                                    //            outline (board edge) instead of POLYGON.
                                    //            Layer is mandatory for polygons (active editor layer cannot be read by a ULP).
                                    //            Layer field replaced by a pulldown of all layers with the editor color swatch.
                                    //            Radius/Distance label and error messages follow the draw type.
                                    //            Fixed endless loop (EAGLE hang) for polygon with Angle step not used/zero/negative.
                                    // 2026-10-11 Phase 1: centralized input validation, actionable error messages,
                                    //            multi-error reporting, and validation for command-line parameters.

enum { DrawWIRE,             // ** do not change this list  **
       DrawPOLYGON,
       DrawMOVE,             // to place Elements in Board
       DrawGROUP,            // Group CUT paste, select all in group ** see also >> dlgGroup("Option") <<
       DrawHOLE,
       DrawPAD,
       DrawSMD
     };

int    DrawType = DrawWIRE;
string cmd_Draw_Info = "<img src=cmd-draw-move-match-none.bmp>";
string Draw_Info     = " ";
string Name_used;
string require = " <font color=\"red\">required</font> ";
string Not_Used = " <font color=\"darkgreen\">not used</font> ";
string Can_Used = " <font color=\"blue\">can be used</font> ";
if (library) Name_used  = Not_Used;
else         Name_used  = Can_Used;


string Para    = "";
string SigName = "";
string width   = "";
string layer   = "";
string Angle_step_used = Not_Used;
string Angle_end_used  = Not_Used;

real   x1, y1, x2;
real   StartAngle     = 0.0;         // start the rotated draw on degree
real   AngleStep      = 0.0;         // angle step in degree to next element or steps at 90° for Ellipse
real   EangleOffset   = 0.0;         // the rotation off the element self + offset
real   EndAngle       = 360.0;       // end the rotated draw on degree
enum   { None, Degreestep, Calcstep };
int    AngleStepTyp   = None;        // flag to calculate the anglestep from count (anglestep)
int    RotateMatch    = 0;           // rotate element with same angle with rotate
int    UseMarkedGroup = 0;
int    Sides          = 0;           // polygon by number of sides (0 = use angle start/end/step)
int    Align          = 0;           // polygon alignment: 0 = use angle start, 1 = flat side horizontal, 2 = flat side vertical
string AlignText[]    = { "None (use angle start)", "Flat side horizontal", "Flat side vertical" };

enum { NONE, CIRCLE, FULL_ELLIPSE, ELLIPSE_4 };
int    Placeform      = NONE;
real   EllipsFactor   = 1.0;         // ratio x to y radius
real   M_EllipsFactor = 1.0;         // copy for menue

//int    polygon      = 0;           // draw ellipse as polygon
//int    smd          = 0;           // place a smd on endpoint
real   SMD_dx         = 0;           // SMD length
real   SMD_dy         = 0;           // SMD width
string PadVia         = "";          // draw Pad or Via as used in editor
string PAD_diameter   = "";          // pad diameter
string Shapes[];
int    ShapeSelect    = PAD_SHAPE_OFFSET+1;

string Drill_Hole     = "";          // drill diameter

string LayerText[];                  // layer pulldown entries, index 0 = no layer
int    LayerNumber[];
int    LayerRGB[];                   // layer color from the editor palette (0x00rrggbb)
int    LayerCount     = 0;
int    LayerSel       = 0;           // selected pulldown entry (0 = keep the current editor layer)

int grid = 1;
string GridUnit[] = { "MIC", "MM", "MIL", "INCH" };
int    gridunit;
real   minx, maxx, miny, maxy;

string Length_Distance_Radius = "&+ radius ";


int PressOk = 0;

string s;
string h;
string Help_Err = "";
string ValidationMessage = "";

string Name1st, NameExt; // use as variable Label in Menu

// ### functions ###
void Set_MinMax_Unit(int Grid) {  // 2012-04-12
  switch(Grid) {
    case GRID_UNIT_MIC  : {  // Micron
                            minx = -1990000;
                            maxx =  1990000;
                            miny = -1990000;
                            maxy =  1990000;
                            break;
                          }
    case GRID_UNIT_MM   : {  // Millimeter
                            minx = -1990;
                            maxx =  1990;
                            miny = -1990;
                            maxy =  1990;
                            break;
                          }
    case GRID_UNIT_MIL  : {  // Mil
                            minx = -78340;
                            maxx =  78340;
                            miny = -78340;
                            maxy =  78340;
                            break;
                          }
    case GRID_UNIT_INCH : {  // Inch
                            minx = -78.34;
                            maxx =  78.34;
                            miny = -78.34;
                            maxy =  78.34;
                            break;
                          }
  }
  return;
}


real u2u(int val) {
  switch (gridunit) {
    case GRID_UNIT_MIC  : return u2mic(val);
    case GRID_UNIT_MM   : return u2mm(val);
    case GRID_UNIT_MIL  : return u2mil(val);
    case GRID_UNIT_INCH : return u2inch(val);
  }
}


void info(void) {
  dlgDialog("cmd-draw HELP") {
    dlgHBoxLayout {
      dlgLabel(usage);
      dlgVBoxLayout {
        dlgLabel("<u>Examples</u>:");
        dlgLabel(Help);
        dlgStretch(1);
        dlgHBoxLayout {
          dlgStretch(1);
          dlgPushButton("+Ok") dlgAccept();
          dlgStretch(1);
        }
      }
    }
  };
  return;
}


// ### layer pulldown ###
void addLayerEntry(int number, string name, int color) {
  string e;
  LayerCount++;
  sprintf(e, "%3d  %s", number, name);
  LayerText[LayerCount]   = e;
  LayerNumber[LayerCount] = number;
  if (color >= 0 && color < PALETTE_ENTRIES) LayerRGB[LayerCount] = palette(color);   // color as currently shown in the editor
  else                                       LayerRGB[LayerCount] = 0;                // out-of-range index would terminate the ULP
  return;
}

// fill the pulldown with the layers of the current editor
void loadLayers(void) {
  LayerText[0]   = "(none - keep current layer)";
  LayerNumber[0] = 0;
  LayerRGB[0]    = 0;
  LayerCount     = 0;
  // inner copper layers 2..15 are listed only if the board really uses them
  if (board) board(B) B.layers(Ly) {
    if (Ly.name && (Ly.number < 2 || Ly.number > 15 || Ly.used)) addLayerEntry(Ly.number, Ly.name, Ly.color);
  }
  if (schematic) schematic(S) S.layers(Ly) {
    if (Ly.name) addLayerEntry(Ly.number, Ly.name, Ly.color);
  }
  if (library) library(LB) LB.layers(Ly) {
    if (Ly.name) addLayerEntry(Ly.number, Ly.name, Ly.color);
  }
  return;
}

// pulldown selection -> layer string used by the script
void syncLayer(void) {
  if (LayerSel > 0) sprintf(layer, "%d", LayerNumber[LayerSel]);
  else              layer = "";
  return;
}

// layer 20 (Dimension) accepts only wires, never polygons
int isDimensionLayer(string l) {
  string u = strupr(l);
  return (u == "20" || u == "DIMENSION");
}


// the length field (x2) is a radius for Wire/Polygon/Move, but the distance from the
// center to the placed element for Pad/Smd/Via/Hole (= radius of the placement circle)
int usesDistance(void) {
  return (DrawType == DrawPAD || DrawType == DrawSMD || DrawType == DrawHOLE || DrawType == DrawGROUP);
}

string lengthName(void) {
  if (usesDistance()) return "Distance";
  return "Radius";
}


// *** Input validation ***
void addValidationError(string message) {
  if (ValidationMessage) {
    ValidationMessage += "\n";
    Help_Err += "<br>";
  }
  ValidationMessage += "- " + message;
  Help_Err += "- " + message;
  return;
}

int error(void) {
  int errors = 0;
  real numericWidth = strtod(width);
  real numericDrill = strtod(Drill_Hole);
  real numericDiameter = strtod(PAD_diameter);

  Help_Err = "";
  ValidationMessage = "";

  // Common geometry checks.
  if (DrawType != DrawGROUP || Placeform != NONE) {
    if (x2 <= 0) {
      if (usesDistance()) addValidationError("Distance must be greater than zero.");
      else addValidationError("Radius must be greater than zero.");
      errors++;
    }
  }

  if (DrawType == DrawWIRE || DrawType == DrawPOLYGON) {
    if (!width || numericWidth <= 0) {
      addValidationError("Wire width is missing or invalid. Enter a width greater than zero.");
      errors++;
    }
  }

  // The selected operation must be supported in the current editor.
  if (DrawType == DrawMOVE && !board) {
    addValidationError("Move is available only in the Board editor.");
    errors++;
  }

  if (DrawType == DrawGROUP) {
    if (!AngleStepTyp) {
      addValidationError("Select an Angle step type: degree step or calculated steps.");
      errors++;
    }
    if (AngleStep == 0) {
      addValidationError("Angle step or number of calculated steps must be greater than zero.");
      errors++;
    }
    if (EndAngle == 0) {
      addValidationError("Angle end must be greater than zero for Group.");
      errors++;
    }
  }

  if (DrawType == DrawSMD) {
    if (board && layer != "1" && layer != "16") {
      addValidationError("SMD layer must be Top (1) or Bottom (16) when drawing on a board.");
      errors++;
    }
    if (SMD_dx < 0 || SMD_dy < 0 ||
        (SMD_dx > 0 && SMD_dy <= 0) || (SMD_dx <= 0 && SMD_dy > 0)) {
      addValidationError("SMD width and height must both be greater than zero, or both be zero to use the current settings.");
      errors++;
    }
  }

  if (DrawType == DrawMOVE && !SigName) {
    addValidationError("Enter the name of the first element to move.");
    errors++;
  }

  if (DrawType == DrawHOLE) {
    if (!Drill_Hole || numericDrill <= 0) {
      addValidationError("Hole drill diameter is missing or invalid. Enter a value greater than zero.");
      errors++;
    }
  }

  if (Drill_Hole && numericDrill <= 0) {
    addValidationError("Drill diameter is invalid. Enter a value greater than zero.");
    errors++;
  }
  if (PAD_diameter && numericDiameter <= 0) {
    addValidationError("Pad/Via diameter is invalid. Enter a value greater than zero.");
    errors++;
  }

  if (DrawType == DrawPOLYGON) {
    if (!layer) {
      addValidationError("Select a layer for the polygon. Use layer 20 (Dimension) for a board outline.");
      errors++;
    }
    if ((Placeform == FULL_ELLIPSE || Placeform == ELLIPSE_4) && EllipsFactor == 1.0) {
      addValidationError("Ellipse factor is missing. Set a value other than 1.0.");
      errors++;
    }
    if (Align && Sides <= 0) {
      addValidationError("Flat-side alignment requires a polygon with a specified number of sides.");
      errors++;
    }
    if (Sides > 0 && Sides < 3) {
      addValidationError("A polygon must have at least 3 sides.");
      errors++;
    }
    if (Sides > 20000) {
      addValidationError("Polygon side count exceeds 20000. Use fewer sides.");
      errors++;
    }
    if (Sides > 0 && Placeform == ELLIPSE_4) {
      addValidationError("Polygon side count cannot be combined with the quarter-ellipse form.");
      errors++;
    }
    if (Sides <= 0) {
      if (!AngleStepTyp) {
        addValidationError("Polygon requires an angle step type or a polygon side count.");
        errors++;
      }
      else if (AngleStep <= 0) {
        if (AngleStepTyp == Calcstep)
          addValidationError("Calculated step count must be greater than zero.");
        else
          addValidationError("Polygon angle step must be greater than zero.");
        errors++;
      }
    }
  }
  else if (DrawType == DrawWIRE && AngleStepTyp) {
    if (AngleStep <= 0) {
      if (AngleStepTyp == Calcstep)
        addValidationError("Calculated step count for Wire must be greater than zero.");
      else
        addValidationError("Wire angle step must be greater than zero.");
      errors++;
    }
  }

  if (AngleStepTyp == Calcstep && AngleStep <= 0 &&
      DrawType != DrawGROUP && DrawType != DrawWIRE && DrawType != DrawPOLYGON) {
    addValidationError("Calculated step count must be greater than zero.");
    errors++;
  }

  if (AngleStepTyp == Calcstep && AngleStep > 0 && EndAngle <= StartAngle &&
      DrawType != DrawPAD && DrawType != DrawSMD && DrawType != DrawHOLE && DrawType != DrawMOVE) {
    addValidationError("End angle must be greater than start angle when using calculated steps.");
    errors++;
  }

  if ((Placeform == FULL_ELLIPSE || Placeform == ELLIPSE_4) &&
      (EllipsFactor <= 0 || EllipsFactor > 100)) {
    addValidationError("Ellipse factor must be greater than zero and no greater than 100.");
    errors++;
  }

  if ((DrawType == DrawPOLYGON || (DrawType == DrawWIRE && AngleStepTyp)) &&
      AngleStepTyp == Calcstep && AngleStep > 20000) {
    addValidationError("Calculated step count exceeds 20000. Use fewer steps.");
    errors++;
  }
  if ((DrawType == DrawPOLYGON || (DrawType == DrawWIRE && AngleStepTyp)) &&
      AngleStepTyp == Degreestep && AngleStep > 0 &&
      (EndAngle - StartAngle) / AngleStep > 20000) {
    addValidationError("The requested geometry would contain more than 20000 vertices. Increase the angle step.");
    errors++;
  }

  return errors;
}


//Image URLS

string cmddrawgroup = "<img src=cmd-draw-group.bmp>"; //cmd-draw-group.bmp

string cmddrawholeellipse4calcstep = "<img src=cmd-draw-hole-ellipse4-calcstep.bmp>"; //cmd-draw-hole-ellipse4-calcstep.bmp

string cmddrawholeellipse4degstep = "<img src=cmd-draw-hole-ellipse4-degstep.bmp>"; //cmd-draw-hole-ellipse4-degstep.bmp

string cmddrawholeellipsecalcstep = "<img src=cmd-draw-hole-ellipse-calcstep.bmp>"; //cmd-draw-hole-ellipse-calcstep.bmp

string cmddrawholeellipsedegstep = "<img src=cmd-draw-hole-ellipse-degstep.bmp>"; //cmd-draw-hole-ellipse-degstep.bmp

string cmddrawholenone = "<img src=cmd-draw-hole-none.bmp>"; //cmd-draw-hole-none.bmp

string cmddrawholenonecalcstep = "<img src=cmd-draw-hole-none-calcstep.bmp>"; //cmd-draw-hole-none-calcstep.bmp

string cmddrawholenonedegstep = "<img src=cmd-draw-hole-none-degstep.bmp>"; //cmd-draw-hole-none-degstep.bmp

string cmddrawmovecirclematchcalcstep = "<img src=cmd-draw-move-circle-match-calcstep.bmp>"; //cmd-draw-move-circle-match-calcstep.bmp

string cmddrawmovecirclematchdegstep = "<img src=cmd-draw-move-circle-match-degstep.bmp>"; //cmd-draw-move-circle-match-degstep.bmp

string cmddrawmovecirclenomatchcalcstep = "<img src=cmd-draw-move-circle-no_match-calcstep.bmp>"; //cmd-draw-move-circle-no_match-calcstep.bmp

string cmddrawmovecirclenomatchdegstep = "<img src=cmd-draw-move-circle-no_match-degstep.bmp>"; //cmd-draw-move-circle-no_match-degstep.bmp

string cmddrawmoveellipse4matchcalcstep = "<img src=cmd-draw-move-ellipse4-match-calcstep.bmp>"; //cmd-draw-move-ellipse4-match-calcstep.bmp

string cmddrawmoveellipse4matchdegstep = "<img src=cmd-draw-move-ellipse4-match-degstep.bmp>"; //cmd-draw-move-ellipse4-match-degstep.bmp

string cmddrawmoveellipse4nomatchcalcstep = "<img src=cmd-draw-move-ellipse4-no_match-calcstep.bmp>"; //cmd-draw-move-ellipse4-no_match-calcstep.bmp

string cmddrawmoveellipse4nomatchdegstep = "<img src=cmd-draw-move-ellipse4-no_match-degstep.bmp>"; //cmd-draw-move-ellipse4-no_match-degstep.bmp

string cmddrawmoveellipsematchcalcstep = "<img src=cmd-draw-move-ellipse-match-calcstep.bmp>"; //cmd-draw-move-ellipse-match-calcstep.bmp

string cmddrawmoveellipsematchdegstep = "<img src=cmd-draw-move-ellipse-match-degstep.bmp>"; //cmd-draw-move-ellipse-match-degstep.bmp

string cmddrawmoveellipsenomatchcalcstep = "<img src=cmd-draw-move-ellipse-no_match-calcstep.bmp>"; //cmd-draw-move-ellipse-no_match-calcstep.bmp

string cmddrawmoveellipsenomatchdegstep = "<img src=cmd-draw-move-ellipse-no_match-degstep.bmp>"; //cmd-draw-move-ellipse-no_match-degstep.bmp

string cmddrawmovematchellipsenone = "<img src=cmd-draw-move-match-ellipse-none.bmp>"; //cmd-draw-move-match-ellipse-none.bmp

string cmddrawmovematchnone = "<img src=cmd-draw-move-match-none.bmp>"; //cmd-draw-move-match-none.bmp

string cmddrawmovenomatchellipsenone = "<img src=cmd-draw-move-no_match-ellipse-none.bmp>"; //cmd-draw-move-no_match-ellipse-none.bmp

string cmddrawmovenomatchnone = "<img src=cmd-draw-move-no_match-none.bmp>"; //cmd-draw-move-no_match-none.bmp

string cmddrawpadellipse4calcstep = "<img src=cmd-draw-pad-ellipse4-calcstep.bmp>"; //cmd-draw-pad-ellipse4-calcstep.bmp

string cmddrawpadellipse4degstep = "<img src=cmd-draw-pad-ellipse4-degstep.bmp>"; //cmd-draw-pad-ellipse4-degstep.bmp

string cmddrawpadellipsecalcstep = "<img src=cmd-draw-pad-ellipse-calcstep.bmp>"; //cmd-draw-pad-ellipse-calcstep.bmp

string cmddrawpadellipsedegstep = "<img src=cmd-draw-pad-ellipse-degstep.bmp>"; //cmd-draw-pad-ellipse-degstep.bmp

string cmddrawpadnone = "<img src=cmd-draw-pad-none.bmp>"; //cmd-draw-pad-none.bmp

string cmddrawpadnonecalcstep = "<img src=cmd-draw-pad-none-calcstep.bmp>"; //cmd-draw-pad-none-calcstep.bmp

string cmddrawpadnonedegstep = "<img src=cmd-draw-pad-none-degstep.bmp>"; //cmd-draw-pad-none-degstep.bmp

string cmddrawpolygoncirclecalcstep = "<img src=cmd-draw-polygon-circle-calcstep.bmp>"; //cmd-draw-polygon-circle-calcstep.bmp

string cmddrawpolygoncircledegstep = "<img src=cmd-draw-polygon-circle-degstep.bmp>"; //cmd-draw-polygon-circle-degstep.bmp

string cmddrawpolygonellipse4calcstep = "<img src=cmd-draw-polygon-ellipse4-calcstep.bmp>"; //cmd-draw-polygon-ellipse4-calcstep.bmp

string cmddrawpolygonellipse4degstep = "<img src=cmd-draw-polygon-ellipse4-degstep.bmp>"; //cmd-draw-polygon-ellipse4-degstep.bmp

string cmddrawpolygonellipse4none = "<img src=cmd-draw-polygon-ellipse4-none.bmp>"; //cmd-draw-polygon-ellipse4-none.bmp

string cmddrawpolygonellipsecalcdeg = "<img src=cmd-draw-polygon-ellipse-calcdeg.bmp>"; //cmd-draw-polygon-ellipse-calcdeg.bmp

string cmddrawpolygonellipsecalcstep = "<img src=cmd-draw-polygon-ellipse-calcstep.bmp>"; //cmd-draw-polygon-ellipse-calcstep.bmp

string cmddrawpolygonellipsedegstep = "<img src=cmd-draw-polygon-ellipse-degstep.bmp>"; //cmd-draw-polygon-ellipse-degstep.bmp

string cmddrawpolygonellipsenone = "<img src=cmd-draw-polygon-ellipse-none.bmp>"; //cmd-draw-polygon-ellipse-none.bmp

string cmddrawpolygonnone = "<img src=cmd-draw-polygon-none.bmp>"; //cmd-draw-polygon-none.bmp

string cmddrawpolygonnonecalcstep = "<img src=cmd-draw-polygon-none-calcstep.bmp>"; //cmd-draw-polygon-none-calcstep.bmp

string cmddrawsmdcirclematchcalcstep = "<img src=cmd-draw-smd-circle-match-calcstep.bmp>"; //cmd-draw-smd-circle-match-calcstep.bmp

string cmddrawsmdcirclematchdegstep = "<img src=cmd-draw-smd-circle-match-degstep.bmp>"; //cmd-draw-smd-circle-match-degstep.bmp

string cmddrawsmdcirclenomatchcalcstep = "<img src=cmd-draw-smd-circle-no_match-calcstep.bmp>"; //cmd-draw-smd-circle-no_match-calcstep.bmp

string cmddrawsmdcriclenomatchdegstep = "<img src=cmd-draw-smd-cricle-no_match-degstep.bmp>"; //cmd-draw-smd-cricle-no_match-degstep.bmp

string cmddrawsmdellipse4matchcalcstep = "<img src=cmd-draw-smd-ellipse4-match-calcstep.bmp>"; //cmd-draw-smd-ellipse4-match-calcstep.bmp

string cmddrawsmdellipse4nomatchcalcstep = "<img src=cmd-draw-smd-ellipse4-no_match-calcstep.bmp>"; //cmd-draw-smd-ellipse4-no_match-calcstep.bmp

string cmddrawsmdellipse4matchdegstep = "<img src=cmd-draw-smd-ellipse4-match-degstep.bmp>"; //cmd-draw-smd-ellipse4-match-degstep.bmp

string cmddrawsmdellipse4nomatchdegstep = "<img src=cmd-draw-smd-ellipse4-no_match-degstep.bmp>"; //cmd-draw-smd-ellipse4-no_match-degstep.bmp

string cmddrawsmdellipsematchcalcstep = "<img src=cmd-draw-smd-ellipse-match-calcstep.bmp>"; //cmd-draw-smd-ellipse-match-calcstep.bmp

string cmddrawsmdellipsematchdegstap = "<img src=cmd-draw-smd-ellipse-match-degstap.bmp>"; //cmd-draw-smd-ellipse-match-degstap.bmp

string cmddrawsmdellipsenomatchcalcstep = "<img src=cmd-draw-smd-ellipse-no_match-calcstep.bmp>"; //cmd-draw-smd-ellipse-no_match-calcstep.bmp

string cmddrawsmdellipsenomatchdegstep = "<img src=cmd-draw-smd-ellipse-no_match-degstep.bmp>"; //cmd-draw-smd-ellipse-no_match-degstep.bmp

string cmddrawsmdmatchdegstep = "<img src=cmd-draw-smd-match-degstep.bmp>"; //cmd-draw-smd-match-degstep.bmp

string cmddrawsmdmatchnone = "<img src=cmd-draw-smd-match-none.bmp>"; //cmd-draw-smd-match-none.bmp

string cmddrawsmdnomatchdegsetp = "<img src=cmd-draw-smd-no_match-degsetp.bmp>"; //cmd-draw-smd-no_match-degsetp.bmp

string cmddrawsmdnomatchnone = "<img src=cmd-draw-smd-no_match-none.bmp>"; //cmd-draw-smd-no_match-none.bmp

string cmddrawwirecalcellipse = "<img src=cmd-draw-wire-calc-ellipse.bmp>"; //cmd-draw-wire-calc-ellipse.bmp

string cmddrawwirecalcstepnone = "<img src=cmd-draw-wire-calcstep-none.bmp>"; //cmd-draw-wire-calcstep-none.bmp

string cmddrawwirecirclecalcstep = "<img src=cmd-draw-wire-circle-calcstep.bmp>"; //cmd-draw-wire-circle-calcstep.bmp

string cmddrawwirecircledegstep = "<img src=cmd-draw-wire-circle-degstep.bmp>"; //cmd-draw-wire-circle-degstep.bmp

string cmddrawwireclacellipse4 = "<img src=cmd-draw-wire-clac-ellipse4.bmp>"; //cmd-draw-wire-clac-ellipse4.bmp

string cmddrawwiredegstepnone = "<img src=cmd-draw-wire-degstep-none.bmp>"; //cmd-draw-wire-degstep-none.bmp

string cmddrawwireellipse = "<img src=cmd-draw-wire-ellipse.bmp>"; //cmd-draw-wire-ellipse.bmp

string cmddrawwirenone = "<img src=cmd-draw-wire-none.bmp>"; //cmd-draw-wire-none.bmp

string cmddrawwirestepellipse = "<img src=cmd-draw-wire-step-ellipse.bmp>"; //cmd-draw-wire-step-ellipse.bmp

string cmddrawwirestepellipse4 = "<img src=cmd-draw-wire-step-ellipse4.bmp>"; //cmd-draw-wire-step-ellipse4.bmp


// *** set info for Menu *** Pictures and Texts ***
void set_Draw_Info(void) {
  Label_Move = " ";
  if (DrawType == DrawWIRE) {
    switch (AngleStepTyp) {
      case None       :
                        Angle_step_used = Not_Used;
                        Angle_end_used  = Not_Used;
                        switch (Placeform) {
                          case NONE         : cmd_Draw_Info = cmddrawwirenone;
                                              break;
                          case CIRCLE       : cmd_Draw_Info = cmddrawwirenone;
                                              break;
                          case FULL_ELLIPSE : cmd_Draw_Info = cmddrawwireellipse;
                                              break;
                          case ELLIPSE_4    : cmd_Draw_Info = cmddrawwireellipse;
                                              break;
                        }
                        break;

      case Degreestep :
                        Angle_step_used = require;
                        Angle_end_used  = require;
                        switch (Placeform) {
                          case NONE         : cmd_Draw_Info = cmddrawwiredegstepnone;
                                              break;
                          case CIRCLE       : cmd_Draw_Info = cmddrawwirecircledegstep;
                                              break;
                          case FULL_ELLIPSE : cmd_Draw_Info = cmddrawwirestepellipse;
                                              break;
                          case ELLIPSE_4    : cmd_Draw_Info = cmddrawwirestepellipse4;
                                              break;
                        }
                        break;
      case Calcstep   :
                        Angle_step_used = require;
                        Angle_end_used  = require;
                        switch (Placeform) {
                          case NONE         : cmd_Draw_Info = cmddrawwirecalcstepnone;
                                              break;
                          case CIRCLE       : cmd_Draw_Info = cmddrawwirecirclecalcstep;
                                              break;
                          case FULL_ELLIPSE : cmd_Draw_Info = cmddrawwirecalcellipse;
                                              break;
                          case ELLIPSE_4    : cmd_Draw_Info = cmddrawwireclacellipse4;
                                              break;
                        }
                        break;
    }
  }

  else if(DrawType == DrawPOLYGON) {
    Angle_step_used = require;
    Angle_end_used  = require;
    switch (AngleStepTyp) {
      case None       : switch (Placeform) {
                          case NONE         : cmd_Draw_Info = cmddrawpolygonnone;
                                              break;
                          case CIRCLE       : cmd_Draw_Info = cmddrawpolygonnone;
                                              break;
                          case FULL_ELLIPSE : cmd_Draw_Info = cmddrawpolygonellipsenone;
                                              break;
                          case ELLIPSE_4    : cmd_Draw_Info = cmddrawpolygonellipse4none;
                                              break;
                        }
                        break;
      case Degreestep : switch (Placeform) {
                          case NONE         : cmd_Draw_Info = cmddrawpolygonnone;
                                              break;
                          case CIRCLE       : cmd_Draw_Info = cmddrawpolygoncircledegstep;
                                              break;
                          case FULL_ELLIPSE : cmd_Draw_Info = cmddrawpolygonellipsedegstep;
                                              break;
                          case ELLIPSE_4    : cmd_Draw_Info = cmddrawpolygonellipse4degstep;
                                              break;
                        }
                        break;
      case Calcstep   : switch (Placeform) {
                          case NONE         : cmd_Draw_Info = cmddrawpolygonnonecalcstep;
                                              break;
                          case CIRCLE       : cmd_Draw_Info = cmddrawpolygoncirclecalcstep;
                                              break;
                          case FULL_ELLIPSE : cmd_Draw_Info = cmddrawpolygonellipsecalcstep;
                                              break;
                          case ELLIPSE_4    : cmd_Draw_Info = cmddrawpolygonellipse4calcstep;
                                              break;
                        }
                        break;
    }
  }

  else if(DrawType == DrawMOVE) {
    if (library || schematic) {
      dlgMessageBox("! MOVE\nYou can use this function only in a Board.", "OK");
    }
    else {
      Label_Move = Help_Move;
      switch (AngleStepTyp) {
        case None       :
                          Angle_step_used = Not_Used;
                          Angle_end_used  = Not_Used;
                          switch (Placeform) {
                            case NONE         : if (!RotateMatch) cmd_Draw_Info = cmddrawmovenomatchnone;
                                                else cmd_Draw_Info = cmddrawmovematchnone;
                                                break;
                            case CIRCLE       : if (!RotateMatch) cmd_Draw_Info = cmddrawmovenomatchnone;
                                                else cmd_Draw_Info = cmddrawmovematchnone;
                                                break;
                            case FULL_ELLIPSE : if (!RotateMatch) cmd_Draw_Info = cmddrawmovenomatchellipsenone;
                                                else cmd_Draw_Info = cmddrawmovematchellipsenone;
                                                break;
                            case ELLIPSE_4    : if (!RotateMatch) cmd_Draw_Info = cmddrawmovenomatchellipsenone;
                                                else cmd_Draw_Info = cmddrawmovematchellipsenone;
                                                break;
                          }
                          break;

        case Degreestep :
                          Angle_step_used = require;
                          Angle_end_used  = require;
                          switch (Placeform) {
                            case NONE         : if (!RotateMatch) cmd_Draw_Info = cmddrawmovenomatchnone;
                                                else cmd_Draw_Info = cmddrawmovematchnone;
                                                break;
                            case CIRCLE       : if (!RotateMatch) cmd_Draw_Info = cmddrawmovecirclenomatchdegstep;
                                                else cmd_Draw_Info = cmddrawmovecirclematchdegstep;
                                                break;
                            case FULL_ELLIPSE : if (!RotateMatch) cmd_Draw_Info = cmddrawmoveellipsenomatchdegstep;
                                                else cmd_Draw_Info = cmddrawmoveellipsematchdegstep;
                                                break;
                            case ELLIPSE_4    : if (!RotateMatch) cmd_Draw_Info = cmddrawmoveellipse4nomatchdegstep;
                                                else cmd_Draw_Info = cmddrawmoveellipse4matchdegstep;
                                                break;
                          }
                          break;

        case Calcstep   :
                          Angle_step_used = require;
                          Angle_end_used  = require;
                          switch (Placeform) {
                            case NONE         : if (!RotateMatch) cmd_Draw_Info = cmddrawmovenomatchnone;
                                                else cmd_Draw_Info = cmddrawmovematchnone;
                                                break;
                            case CIRCLE       : if (!RotateMatch) cmd_Draw_Info = cmddrawmovecirclenomatchcalcstep;
                                                else cmd_Draw_Info = cmddrawmovecirclematchcalcstep;
                                                break;
                            case FULL_ELLIPSE : if (!RotateMatch) cmd_Draw_Info = cmddrawmoveellipsenomatchcalcstep;
                                                else cmd_Draw_Info = cmddrawmoveellipsematchcalcstep;
                                                break;
                            case ELLIPSE_4    : if (!RotateMatch) cmd_Draw_Info = cmddrawmoveellipse4nomatchcalcstep;
                                                else cmd_Draw_Info = cmddrawmoveellipse4matchcalcstep;
                                                break;
                          }
                          break;
      }
    }
  }

  else if(DrawType == DrawGROUP) {
    Angle_step_used = require;
    Angle_end_used  = require;
    cmd_Draw_Info = cmddrawgroup;
  }

  else if(DrawType == DrawPAD) {
    Label_Move = Help_Move;
    switch (AngleStepTyp) {
      case None       :
                        Angle_step_used = Not_Used;
                        Angle_end_used  = Not_Used;
                        switch (Placeform) {
                          case NONE         : cmd_Draw_Info = cmddrawpadnone;
                                              break;
                          case CIRCLE       : cmd_Draw_Info = cmddrawpadnone;
                                              break;
                          case FULL_ELLIPSE : cmd_Draw_Info = cmddrawpadnone;
                                              break;
                          case ELLIPSE_4    : cmd_Draw_Info = cmddrawpadnone;
                                              break;
                        }
                        break;

      case Degreestep :
                        Angle_step_used = require;
                        Angle_end_used  = require;
                        switch (Placeform) {
                          case NONE         : cmd_Draw_Info = cmddrawpadnonedegstep;
                                              break;
                          case CIRCLE       : cmd_Draw_Info = cmddrawpadnonedegstep;
                                              break;
                          case FULL_ELLIPSE : cmd_Draw_Info = cmddrawpadellipsedegstep;
                                              break;
                          case ELLIPSE_4    : cmd_Draw_Info = cmddrawpadellipse4degstep;
                                              break;
                        }
                        break;

      case Calcstep   :
                        Angle_step_used = require;
                        Angle_end_used  = require;
                        switch (Placeform) {
                          case NONE         : cmd_Draw_Info = cmddrawpadnonecalcstep;
                                              break;
                          case CIRCLE       : cmd_Draw_Info = cmddrawpadnonecalcstep;
                                              break;
                          case FULL_ELLIPSE : cmd_Draw_Info = cmddrawpadellipsecalcstep;
                                              break;
                          case ELLIPSE_4    : cmd_Draw_Info = cmddrawpadellipse4calcstep;
                                              break;
                        }
                        break;
    }
  }

  else if(DrawType == DrawSMD) {
    Label_Move = Help_Move;
    switch (AngleStepTyp) {
      case None       :
                        Angle_step_used = Not_Used;
                        Angle_end_used  = Not_Used;
                        switch (Placeform) {
                          case NONE         : if (!RotateMatch) cmd_Draw_Info = cmddrawsmdnomatchnone;
                                              else cmd_Draw_Info = cmddrawsmdmatchnone;
                                              break;
                          case CIRCLE       : if (!RotateMatch) cmd_Draw_Info = cmddrawsmdnomatchnone;
                                              else cmd_Draw_Info = cmddrawsmdmatchnone;
                                              break;
                          case FULL_ELLIPSE : if (!RotateMatch) cmd_Draw_Info = cmddrawsmdnomatchnone;
                                              else cmd_Draw_Info = cmddrawsmdmatchnone;
                                              break;
                          case ELLIPSE_4    : if (!RotateMatch) cmd_Draw_Info = cmddrawsmdnomatchnone;
                                              else cmd_Draw_Info = cmddrawsmdmatchnone;
                                              break;
                        }
                        break;

      case Degreestep :
                        Angle_step_used = require;
                        Angle_end_used  = require;
                        switch (Placeform) {
                          case NONE         : if (!RotateMatch) cmd_Draw_Info = cmddrawsmdnomatchdegsetp;
                                              else cmd_Draw_Info = cmddrawsmdmatchdegstep;
                                              break;
                          case CIRCLE       : if (!RotateMatch) cmd_Draw_Info = cmddrawsmdcriclenomatchdegstep;
                                              else cmd_Draw_Info = cmddrawsmdcirclematchdegstep;
                                              break;
                          case FULL_ELLIPSE : if (!RotateMatch) cmd_Draw_Info = cmddrawsmdellipsenomatchdegstep;
                                              else cmd_Draw_Info = cmddrawsmdellipsematchdegstap;
                                              break;
                          case ELLIPSE_4    : if (!RotateMatch) cmd_Draw_Info = cmddrawsmdellipse4nomatchdegstep;
                                              else cmd_Draw_Info = cmddrawsmdellipse4matchdegstep;
                                              break;
                        }
                        break;

      case Calcstep   :
                        Angle_step_used = require;
                        Angle_end_used  = require;
                        switch (Placeform) {
                          case NONE         : if (!RotateMatch) cmd_Draw_Info = cmddrawsmdnomatchnone;
                                              else cmd_Draw_Info = cmddrawsmdmatchnone;
                                              break;
                          case CIRCLE       : if (!RotateMatch) cmd_Draw_Info = cmddrawsmdcirclenomatchcalcstep;
                                              else cmd_Draw_Info = cmddrawsmdcirclematchcalcstep;
                                              break;
                          case FULL_ELLIPSE : if (!RotateMatch) cmd_Draw_Info = cmddrawsmdellipsenomatchcalcstep;
                                              else cmd_Draw_Info = cmddrawsmdellipsematchcalcstep;
                                              break;
                          case ELLIPSE_4    : if (!RotateMatch) cmd_Draw_Info = cmddrawsmdellipse4nomatchcalcstep;
                                              else cmd_Draw_Info = cmddrawsmdellipse4matchcalcstep;
                                              break;
                        }
    }
  }

  else if(DrawType == DrawHOLE) {
    switch (AngleStepTyp) {
      case None       :
                        Angle_step_used = Not_Used;
                        Angle_end_used  = Not_Used;
                        switch (Placeform) {
                          case NONE         : cmd_Draw_Info = cmddrawholenone;
                                              break;
                          case CIRCLE       : cmd_Draw_Info = cmddrawholenone;
                                              break;
                          case FULL_ELLIPSE : cmd_Draw_Info = cmddrawholenone;
                                              break;
                          case ELLIPSE_4    : cmd_Draw_Info = cmddrawholenone;
                                              break;
                        }
                        break;

      case Degreestep :
                        Angle_step_used = require;
                        Angle_end_used  = require;
                        switch (Placeform) {
                          case NONE         : cmd_Draw_Info = cmddrawholenonedegstep;
                                              break;
                          case CIRCLE       : cmd_Draw_Info = cmddrawholenonedegstep;
                                              break;
                          case FULL_ELLIPSE : cmd_Draw_Info = cmddrawholeellipsedegstep;
                                              break;
                          case ELLIPSE_4    : cmd_Draw_Info = cmddrawholeellipse4degstep;
                                              break;
                        }
                        break;

      case Calcstep   :
                        Angle_step_used = require;
                        Angle_end_used  = require;
                        switch (Placeform) {
                          case NONE         : cmd_Draw_Info = cmddrawholenonecalcstep;
                                              break;
                          case CIRCLE       : cmd_Draw_Info = cmddrawholenonecalcstep;
                                              break;
                          case FULL_ELLIPSE : cmd_Draw_Info = cmddrawholeellipsecalcstep;
                                              break;
                          case ELLIPSE_4    : cmd_Draw_Info = cmddrawholeellipse4calcstep;
                                              break;
                        }
                        break;
    }
  }

  if (DrawType == DrawGROUP) {
    Angle_step_used = require;
    Angle_end_used  = require;
    cmd_Draw_Info = cmddrawgroup;
    RotateMatch = 1;
  }
  else if (DrawType != DrawMOVE && PadVia == "VIA") {
    RotateMatch = 0;
  }
  return;
}



// ****** main menu ******
int menue(void) {
  int RESULT;
  // label always follows the draw type (radius or distance), not the order of the clicks
  if (DrawType == DrawGROUP && Placeform == NONE) Length_Distance_Radius = " not used "; // 2012-04-12
  else if (usesDistance())                         Length_Distance_Radius = "&+ distance ";
  else                                             Length_Distance_Radius = "&+ radius ";

  Name1st = " ";
  NameExt = " ";
  if (board && DrawType == DrawMOVE) {
    Name1st = " &- 1st. Element ";
    NameExt = " name";
  }
  if (board && DrawType == DrawWIRE) {
    Name1st = " &- Signal ";
    NameExt = " name";
  }
  if (package && DrawType == DrawPAD) {
    Name1st = " &- 1st. Pad ";
    NameExt = " name";
  }
  if (board && DrawType == DrawPAD) {
    Name1st = " &- Signal ";
    NameExt = " name";
  }
  if (package && DrawType == DrawSMD) {
    Name1st = " &- 1st. Smd ";
    NameExt = " name";
  }
  if (package && DrawType == DrawMOVE || package && DrawType == DrawWIRE) {
    Name1st = " ";
    NameExt = " ";
  }
  if (schematic && DrawType != DrawPOLYGON) {
    Name1st = " &- Net name ";
    NameExt = " ";
  }

  string LayerSwatch = " ";
  if (LayerSel > 0) {
    sprintf(LayerSwatch, "<table border=1 cellpadding=0><tr><td bgcolor=\"#%06x\">&nbsp;&nbsp;&nbsp;&nbsp;&nbsp;&nbsp;&nbsp;&nbsp;</td></tr></table>", LayerRGB[LayerSel]);
  }

  RESULT = dlgDialog("Command Draw") {
      dlgVBoxLayout {
        dlgHBoxLayout {
          dlgSpacing (8);
          dlgLabel (Draw_Info, 1);
        }
        dlgHBoxLayout {
          dlgGroup("Option") {
            set_Draw_Info();
            dlgGridLayout {

              dlgCell(  1, 1) dlgHBoxLayout dlgSpacing(10);
              dlgCell(  1, 4) dlgHBoxLayout dlgSpacing(10);

              if (DrawType == DrawWIRE || DrawType == DrawPOLYGON) {
                dlgCell(  5, 2) dlgLabel( "&Width ");
                dlgCell(  5, 3) dlgStringEdit( width);
              }
              if (DrawType == DrawWIRE || DrawType == DrawPOLYGON || DrawType == DrawSMD || DrawType == DrawMOVE) {
                dlgCell(  5, 5) dlgLabel(" &Layer");
                dlgCell(  5, 6) dlgComboBox(LayerText, LayerSel) { dlgAccept(); }   // redraw to update the color swatch
                dlgCell(  5, 7) dlgLabel(LayerSwatch);
              }

              dlgCell(  5, 8) dlgLabel(Name1st, 1);
              if ( Name1st != " ") {
                dlgCell(  5, 9) dlgStringEdit(SigName);     // Signal-, Element-, Net-Name
              }
              dlgCell(  5, 10) dlgLabel(NameExt ,1);

              dlgCell(  7, 2) dlgLabel( "&X center coord. ");
              dlgCell(  7, 3) dlgRealEdit( x1, minx, maxx);
              dlgCell(  7, 5) dlgLabel( "&Y center coord. ");
              dlgCell(  7, 6) dlgRealEdit( y1, miny, maxy);
              dlgCell(  7, 8) dlgHBoxLayout { dlgLabel( Length_Distance_Radius, 1); dlgStretch(1); }
              dlgCell(  7, 9) dlgHBoxLayout { dlgRealEdit( x2, 0, maxx); dlgStretch(1); }

              dlgCell(  8, 2) dlgLabel("Angle st&art ° ");
              dlgCell(  8, 3) dlgRealEdit( StartAngle, 0.0, 720.0); // 2010-10-15
              dlgCell(  8, 5) dlgLabel("A&ngle step ");
              dlgCell(  8, 6) dlgRealEdit( AngleStep, -360.0, 360.0);
              dlgCell(  8, 7) dlgSpacing(12);
              dlgCell(  8, 8) dlgLabel(" Angle &end ° ");
              dlgCell(  8, 9) dlgRealEdit( EndAngle, 0.0, 720.0);
              dlgCell(  8,10) dlgSpacing(50);

              dlgCell(  9, 0) dlgVBoxLayout dlgSpacing(12);
              dlgCell(  9, 3) if(DrawType == DrawGROUP) {  // 2011-10-21
                                dlgCheckBox("Use selected group", UseMarkedGroup);
                              }
              dlgCell(  9, 6) dlgLabel(Angle_step_used, 1);
              dlgCell(  9, 9) dlgLabel(Angle_end_used, 1);
              if (DrawType == DrawPOLYGON) {   // number of sides instead of angle end/step
                dlgCell( 10, 2) dlgLabel(" Polygon si&des ");
                dlgCell( 10, 3) dlgIntEdit(Sides, 0, 20000);
                dlgCell( 10, 5) dlgLabel(" 0 = use angles; if set, angle step/end are ignored ");
                dlgCell( 11, 2) dlgLabel(" Ali&gn flat side ");
                dlgCell( 11, 3) dlgComboBox(AlignText, Align);
                dlgCell( 11, 5) dlgLabel(" parallel to the screen; overrides angle start ");
              }


              dlgCell(  5, 0) dlgRadioButton("Wire &1 ", DrawType) {
                Draw_Info = " ";
                if (library) Name_used  = Not_Used;
                else         Name_used  = " ";
                //Length_Distance_Radius = "&+ radius ";
                dlgReject();
                dlgAccept();
              }
              dlgCell(  6, 0) dlgRadioButton("P&olygon ", DrawType) {
                Draw_Info = " ";
                if (library) Name_used  = Not_Used;
                else         Name_used  = " ";
                //Length_Distance_Radius = "&+ radius ";
                dlgAccept();
              }
              dlgCell(  6, 9) dlgLabel(Name_used, 1);

              dlgCell(  7, 0) dlgRadioButton("&Move ", DrawType) {  // 2006.07.06 alf@cadsoft.de
                Draw_Info = "MOVE Elements by Name";
                Name_used  = require;
                //Length_Distance_Radius = "&+ radius ";
                dlgAccept();
              }

              dlgCell(  8, 0) dlgRadioButton("&Group *", DrawType) {
                Draw_Info = "GROUP CUT all elements displayed and PASTE (rotated).";
                Name_used  = " ";
                Length_Distance_Radius = "&+ distance ";
                RotateMatch = 1;
                dlgAccept();
              }

              if (board || package) {
                dlgCell( 12, 0) dlgRadioButton("&Hole ", DrawType) {
                  Draw_Info = " ";
                  Name_used  = " ";
                  Length_Distance_Radius = "&+ distance ";   // FIX: was "%+"
                  dlgAccept();
                }
                if (DrawType == DrawPAD || DrawType == DrawHOLE) {
                  if (DrawType == DrawHOLE) {
                    dlgCell( 12, 2) dlgLabel( " Hole d&rill ");
                  }
                  if (DrawType == DrawPAD) {
                    if (package) {
                      dlgCell( 12, 2) dlgLabel( " Pad d&rill ");
                    }
                    if (board) {
                      dlgCell( 12, 2) dlgLabel( " Via d&rill ");
                    }
                  }
                  dlgCell( 12, 3) dlgStringEdit( Drill_Hole);
                }
              }

              if (package) {
                PadVia = "PAD";
                Shapes[PAD_SHAPE_SQUARE]  = "Square";
                Shapes[PAD_SHAPE_ROUND]   = "Round";
                Shapes[PAD_SHAPE_OCTAGON] = "Octagon";
                Shapes[PAD_SHAPE_LONG]    = "Long";
                Shapes[PAD_SHAPE_OFFSET]  = "Offset";
                Shapes[PAD_SHAPE_OFFSET+1] = " ";  // last must be empty

                dlgCell( 13, 0) dlgRadioButton("&Pad ", DrawType) {
                  Draw_Info = " ";
                  Name_used  = " can be used";
                  Length_Distance_Radius = "&+ distance ";
                  dlgAccept();
                }
                if (DrawType == DrawPAD) {
                  dlgCell( 13, 2) dlgLabel( " PAD &Diameter ");
                  dlgCell( 13, 3) dlgStringEdit( PAD_diameter);
                  dlgCell( 13, 5) dlgLabel( " Shape ");
                  dlgCell( 13, 6) dlgComboBox(Shapes, ShapeSelect);
                }
                dlgCell( 14, 0) dlgRadioButton("&Smd ", DrawType) {
                  Draw_Info = " ";
                  Name_used  = " ";
                  Length_Distance_Radius = "&+ distance ";
                  dlgAccept();
                }
                if (DrawType == DrawSMD) {
                  dlgCell( 14, 2) dlgLabel( " &Wide dx ");
                  dlgCell( 14, 3) dlgRealEdit( SMD_dx);
                  dlgCell( 14, 5) dlgLabel( " Heigh&t dy ");
                  dlgCell( 14, 6) dlgRealEdit( SMD_dy);
                }
              }

              if (board) {
                PadVia = "VIA";
                Shapes[PAD_SHAPE_SQUARE]  = "Square";
                Shapes[PAD_SHAPE_ROUND]   = "Round";
                Shapes[PAD_SHAPE_OCTAGON] = "Octagon";
                Shapes[PAD_SHAPE_OCTAGON+1] = " ";
                ShapeSelect = PAD_SHAPE_OCTAGON+1;

                dlgCell( 13, 0) dlgRadioButton("&Via ", DrawType) {  // ** Via in Board / Pad in Package  **
                  Draw_Info = " ";
                  Name_used  = " can be used";
                  Length_Distance_Radius = "&+ distance ";
                  RotateMatch = 0;
                  dlgAccept();
                }
                if (DrawType == DrawPAD) {
                  dlgCell( 13, 2) dlgLabel( " VIA &Diameter ");
                  dlgCell( 13, 3) dlgStringEdit( PAD_diameter);
                  dlgCell( 13, 5) dlgLabel( " Shape ");
                  dlgCell( 13, 6) dlgComboBox(Shapes, ShapeSelect);
                }
              }
            }
          }
          dlgStretch(1);
        }
        dlgSpacing(8);
        dlgHBoxLayout {
          dlgLabel(cmd_Draw_Info, 1);   // picture for info (local .bmp files)
          dlgGroup("Angle step type") {
            dlgRadioButton("Not used ", AngleStepTyp)  set_Draw_Info();
            dlgRadioButton("&° degree step ", AngleStepTyp)  set_Draw_Info();
            dlgRadioButton("&/ calc. steps ", AngleStepTyp)  set_Draw_Info();
            dlgLabel(" ");
            if (DrawType == DrawMOVE || DrawType == DrawSMD ) {
              dlgCheckBox("Rotate &item to match ", RotateMatch) {
                set_Draw_Info();
              }
              dlgHBoxLayout {
                dlgLabel( " I&tem ");
                dlgRealEdit(EangleOffset, 0.0, 359.9);
                dlgLabel( " rotate offset");
              }
            }
          }
          dlgGroup("Form") {
            dlgHBoxLayout {
              //set_Draw_Info();
              dlgRadioButton("Not &Used", Placeform) {
                set_Draw_Info();
                if (EllipsFactor != 1.0) {
                  M_EllipsFactor = EllipsFactor;
                  EllipsFactor = 1;
                }
              }
              dlgRadioButton("&Circle", Placeform) {
                set_Draw_Info();
                if (EllipsFactor != 1.0) {
                  M_EllipsFactor = EllipsFactor;
                  EllipsFactor = 1;
                }
              }
              dlgRadioButton("Full ellipse &0", Placeform) {
                set_Draw_Info();
                if (EllipsFactor != 1.0) {
                  M_EllipsFactor = EllipsFactor;
                }
                else EllipsFactor = M_EllipsFactor;
              }
              dlgRadioButton("1/&4 ellipse", Placeform) {
                set_Draw_Info();
                if (EllipsFactor != 1.0) {
                  M_EllipsFactor = EllipsFactor;
                }
                else EllipsFactor = M_EllipsFactor;
              }
              dlgStretch(1);
            }
            dlgSpacing(8);
            dlgHBoxLayout {
              dlgLabel( " Ellipse &factor y = x*f ");
              dlgRealEdit( EllipsFactor, +0.01, +100.0);
            }
          }
          dlgStretch(1);
        }
      }

      dlgHBoxLayout {
        dlgLabel("<font color=\"blue\"><b>Grid " + GridUnit[grid] + "</b></font>");
        dlgSpacing(12);
        dlgLabel(Mark_Info);
        dlgStretch(1);
      }
      dlgLabel(Label_Move, 1);
      if (DrawType == DrawPOLYGON) {
        dlgLabel("<nobr><font color=\"blue\">Polygon: choose the Layer. On layer 20 (Dimension, wires only) a closed WIRE outline is drawn (uses Width).</font></nobr>", 1);
      }
      dlgHBoxLayout {
        dlgLabel("<nobr><font color=\"red\">" + Help_Err + "</font><nobr>", 1);
        dlgStretch(1);
      }
      dlgHBoxLayout {
        dlgPushButton("+OK") {
          dlgAccept();
          PressOk = 1;
        }
        dlgPushButton("-Cancel") { dlgReject(); exit(0); }
        dlgStretch(1);
        dlgLabel(Version);
        dlgPushButton("Help") info();
      }
  };
  return RESULT;
}


string getPrefix(string s) {
  int l = strlen(s);
  string prfx;
  for (int n = 0; n <= l; n++) {
    if (s[n] < '0' || s[n] > '9');
    else {
      prfx = strsub(s, 0, n);
      break;
    }
  }
  return prfx;
}


int getNumber(string s) {
  int l = strlen(s);
  for (int n = 0; n <= l; n++) {
    if (s[n] < '0' || s[n] > '9');
    else return strtol(strsub(s, n));
  }
  return 0;
}


// if Element in Project
int exist(string e) {
  board(B) {
    B.elements(E) {
      if (E.name == e) return 1;
    }
  }
  return 0;
}


// ** draw wire Ellipse **
string wireEllipse(void) {
  string e;
  real rad;
  string xystart;
  int    start = 1;
  for (real angle = StartAngle; angle <= EndAngle; angle += AngleStep) {
    rad = PI / 180 * angle;
    sprintf(h, "(R%.9f %.9f)\n",
                    x1 + (cos(rad) * x2),
                    y1 + (sin(rad) * x2 * EllipsFactor) );
    e += h;
    if (start) {
      xystart = h;
      start = 0;
    }
  }
  if (DrawType == DrawPOLYGON && AngleStepTyp != None) {
    e += xystart;
  }
  return e;
}


// *** generate Script to draw WIRE ***
void drawWire(void) {
  if (board && SigName) SigName = "'"+SigName+"'";
  if (library) SigName = "";

  real rad = PI / 180 * StartAngle;
  real a;

  if (AngleStepTyp) {
    switch(Placeform) {
      case NONE         :
                          for (a = StartAngle; a <= EndAngle; a += AngleStep) {
                            rad = PI / 180 * a;
                            sprintf(h, "WIRE %s %s (R%.9f %.9f) (R%.9f %.9f);\n",
                                        width, SigName,
                                        x1, y1,
                                        x1 + (cos(rad) * x2),
                                        y1 + (sin(rad) * x2 * EllipsFactor) );
                            s += h;
                          }
                          break;
      case CIRCLE       :
                          sprintf(h, "WIRE %s %s ", width, SigName);
                          s += h;
                          for (a = StartAngle; a <= EndAngle; a += AngleStep) {
                            rad = PI / 180 * a;
                            sprintf(h, " (R%.9f %.9f) ", x1 + (cos(rad) * x2), y1 + (sin(rad) * x2 * EllipsFactor) );
                            s += h;
                          }
                          s += ";\n";
                          break;
      case FULL_ELLIPSE :
                          sprintf(h, "WIRE %s %s ", width, SigName);
                          s += h;
                          s += wireEllipse() + ";\n";
                          break;
      case ELLIPSE_4    :
                          sprintf(h, "WIRE %s %s ", width, SigName);
                          s += h;
                          s += wireEllipse() + ";\n";
                          break;
    }
  }
  else {
    sprintf(h, "WIRE %s %s (R%.9f %.9f) (R%.9f %.9f);\n",
                     width, SigName,
                     x1, y1,
                     x1 + (cos(rad) * x2),
                     y1 + (sin(rad) * x2 * EllipsFactor) );
    s += h;
  }
  return;
}


// ** draw Polygon ***
void drawPolygon(void) {
  if (board && SigName) SigName = "'"+SigName+"'";
  if (library) SigName = "";

  if((Placeform == FULL_ELLIPSE || Placeform == ELLIPSE_4) && EllipsFactor == 1.0) {
    dlgMessageBox("!Ellipse factor missing: set a value other than 1.0", "OK");
    exit(-2);
  }
  // layer 20 (Dimension) accepts only wires: draw the closed outline with WIRE instead of POLYGON
  if (!layer) {
    dlgMessageBox("!Layer required for Polygon (the active editor layer cannot be read).\nUse the L parameter, e.g. L20", "OK");
    exit(-2);
  }
  string DrawCmd = "POLYGON";
  if (isDimensionLayer(layer)) {
    DrawCmd = "WIRE";
    SigName = "";
  }
  string ecmd;

  if (AngleStepTyp) {
    switch(Placeform) {
      case NONE         :
                          sprintf(ecmd, "%s %s %s ", DrawCmd, width, SigName );
                          s += ecmd;
                          s += wireEllipse();
                          s += ";\n";   // FIX: terminate the command
                          break;
      case CIRCLE       :
                          sprintf(ecmd, "%s %s %s ", DrawCmd, width, SigName );
                          s += ecmd;
                          s += wireEllipse();
                          s += ";\n";
                          break;
      case FULL_ELLIPSE :
                          sprintf(ecmd, "%s %s %s ", DrawCmd, width, SigName );
                          s += ecmd;
                          s += wireEllipse();
                          s += ";\n";
                          break;
      case ELLIPSE_4    :
                          sprintf(ecmd, "%s %s %s ", DrawCmd, width, SigName );
                          s += ecmd;
                          s += wireEllipse();
                          s += ";\n";
                          break;
    }
  }
  else {
    switch(Placeform) {
      case NONE         :
                          sprintf(ecmd, "%s %s %s ", DrawCmd, width, SigName );
                          s += ecmd;
                          sprintf(ecmd, " (R%.9f %.9f)\n", x1, y1 );
                          s += ecmd;
                          s += wireEllipse();
                          s += ecmd +";\n";
                          break;
      case CIRCLE       :
                          sprintf(ecmd, "%s %s %s ", DrawCmd, width, SigName );
                          s += ecmd;
                          sprintf(ecmd, " (R%.9f %.9f)\n", x1, y1 );
                          s += ecmd;
                          s += wireEllipse();
                          s += ecmd;
                          s += ";\n";
                          break;
      case FULL_ELLIPSE :
                          sprintf(ecmd, "%s %s %s ", DrawCmd, width, SigName );
                          s += ecmd;
                          sprintf(ecmd, " (R%.9f %.9f)\n", x1, y1 );
                          s += ecmd;
                          s += wireEllipse();
                          s += ecmd;
                          s += ";\n";
                          break;
      case ELLIPSE_4    :
                          sprintf(ecmd, "%s %s %s ", DrawCmd, width, SigName );
                          s += ecmd;
                          sprintf(ecmd, " (R%.9f %.9f)\n", x1, y1 );
                          s += ecmd;
                          s += wireEllipse();
                          s += ecmd;
                          s += ";\n";
                          break;
    }
  }
  return ;
}


// *** generate Script to MOVE packages ***
void drawMove(void) {
  real rad = PI / 180 * StartAngle;
  string Prefix = getPrefix(SigName);
  int    NameCount = getNumber(SigName);
  string m = "";
  if (layer == "16") {
    m = "M";   // to mirror the Element
  }

  if (AngleStepTyp) {
    if (AngleStep < 0) {
      if (StartAngle < EndAngle) StartAngle+= 360;
      for (real a = StartAngle; a > EndAngle; a += AngleStep) {
        string eName;
        sprintf(eName, "%s%d", Prefix, NameCount);
        if (exist(eName)) {
          rad = PI / 180 * a;
          sprintf(h, "MOVE '%s' (R%.9f %.9f);\n",
                      eName,
                      x1 + (cos(rad) * x2),
                      y1 + (sin(rad) * x2 * EllipsFactor)
                 );
          s += h;
          real ang = 0;
          if (RotateMatch) {
            if (m) ang = 180.0 - a;
            else ang = a;
          }
          sprintf(h, "ROTATE =%sR%.2f '%s';\n", m, ang+EangleOffset, eName);
          s += h;
          NameCount++;
        }
        else break;
      }
    }
    else {
      for (real a = StartAngle; a < EndAngle; a += AngleStep) {
        string eName;
        sprintf(eName, "%s%d", Prefix, NameCount);
        if (exist(eName)) {
          rad = PI / 180 * a;
          sprintf(h, "MOVE '%s' (R%.9f %.9f);\n", eName,
                  x1 + (cos(rad) * x2),
                  y1 + (sin(rad) * x2 * EllipsFactor) );
          s += h;
          real ang = 0;
          if (RotateMatch) {
            if (m) ang = 180.0 - a;
            else ang = a;
          }
          sprintf(h, "ROTATE =%sR%.2f '%s';\n", m, ang+EangleOffset, eName);   // FIX: add offset
          s += h;
          NameCount++;
        }
        else break;
      }
    }
  }
  else {
    if (exist(SigName)) {
      sprintf(h, "MOVE '%s' (R%.9f %.9f);\n", SigName,
                  x1 + (cos(rad) * x2),
                  y1 + (sin(rad) * x2 * EllipsFactor) );
      s += h;
      real ang = StartAngle;
      if (RotateMatch) {
        if (m) ang = 180.0 - StartAngle;
        else ang = StartAngle;
      }
      else ang = 0;
      sprintf(h, "ROTATE =%sR%.2f '%s';\n", m, ang+EangleOffset, SigName);   // FIX: add offset
      s += h;
    }
  }
  return;
}


// FIX: SMD rotation including the rotate offset (same rule as MOVE)
real smdRotation(real a) {
  if (RotateMatch) return a + EangleOffset;
  return EangleOffset;
}

// *** generate Script to place SMDs ***
void drawSmd(void) {
  if (SigName) SigName = "'"+SigName+"'";
  if (SMD_dx && SMD_dy) {
    sprintf(h, "CHANGE SMD %.9f %.9f;\n", SMD_dx, SMD_dy);
    s += h;
  }
  real rad = PI / 180 * StartAngle;
  if (AngleStep) {
    if (AngleStep < 0) {
      if (StartAngle < EndAngle) StartAngle+= 360;   // FIX: was ">" (inverted)
      for (real a = StartAngle; a > EndAngle; a += AngleStep) {
        rad = PI / 180 * a;
        if (EAGLE_VERSION >= 4 && EAGLE_RELEASE >= 10 || EAGLE_VERSION >= 5) {
          string rm = "";
          if (RotateMatch || EangleOffset) sprintf(rm, "R%.2f", smdRotation(a));
          sprintf(h, "SMD %s %s (R%.9f %.9f);\n",         // 2008-05-06
                     rm,
                     SigName,
                     x1 + (cos(rad) * x2),
                     y1 + (sin(rad) * x2 * EllipsFactor)
                 );
          s += h;
        }
        else {
          sprintf(h, "SMD (R%.9f %.9f);\n",
                     x1 + (cos(rad) * x2),
                     y1 + (sin(rad) * x2 * EllipsFactor)
                 );
          s += h;
        }
        if (SigName) SigName = "";         // 2008-05-06
      }
    }
    else {
      for (real a = StartAngle; a < EndAngle; a += AngleStep) {
        rad = PI / 180 * a;
        if (EAGLE_VERSION >= 4 && EAGLE_RELEASE >= 10 || EAGLE_VERSION >= 5) {
          string rm;
          if (RotateMatch || EangleOffset) sprintf(rm, "R%.2f", smdRotation(a));
          sprintf(h, "SMD %s %s (R%.9f %.9f);\n",          // 2008-05-06
                     rm,
                     SigName,
                     x1 + (cos(rad) * x2),
                     y1 + (sin(rad) * x2 * EllipsFactor)
                 );
          s += h;
          if (SigName) SigName = "";         // 2008-05-06
        }
        else {
          sprintf(h, "SMD (R%.9f %.9f);\n",
                     x1 + (cos(rad) * x2),
                     y1 + (sin(rad) * x2 * EllipsFactor)
                 );
          s += h;
        }
      }
    }
  }
  else {
    if (EAGLE_VERSION >= 4 && EAGLE_RELEASE >= 10 || EAGLE_VERSION >= 5) {
      string rm;
      if (RotateMatch || EangleOffset) sprintf(rm, "R%.2f", smdRotation(StartAngle));

      sprintf(h, "SMD %s %s (R%.9f %.9f);\n",         // 2008-05-06
                  rm,
                  SigName,
                  x1 + (cos(rad) * x2),
                  y1 + (sin(rad) * x2 * EllipsFactor)
             );
      s+= h;
      if (SigName) SigName = "";         // 2008-05-06
    }
    else {
      sprintf(h, "SMD (R%.9f %.9f);\n",
                  x1 + (cos(rad) * x2),
                  y1 + (sin(rad) * x2 * EllipsFactor)
             );
      s+= h;
    }
  }
  return ;
}


// *** generate Script to place PADs ***
void drawPad(void) {
  if (SigName) SigName = "'"+SigName+"'";
  real rad = PI / 180 * StartAngle;
  if (PadVia == "PAD" || PadVia == "VIA") { // 2013-08-05 change shape also for Via
    if (ShapeSelect < PAD_SHAPE_OFFSET+1 && Shapes[ShapeSelect] != " ")   // FIX: skip blank entry
    s += "CHANGE SHAPE " + Shapes[ShapeSelect] + ";\n";
  }
  string Rotate_option = "";
  if (AngleStep) {
    string h;
    if (AngleStep < 0) {
      if (StartAngle < EndAngle) StartAngle+= 360;
      for (real a = StartAngle; a > EndAngle; a += AngleStep) {
        rad = PI / 180 * a;
        if (PadVia == "PAD") sprintf(Rotate_option, "R%.2f", a);
        if (EAGLE_VERSION >= 4 && EAGLE_RELEASE >= 10 || EAGLE_VERSION >= 5) {
          sprintf(h, "%s %s %s (R%.9f %.9f);\n", PadVia, Rotate_option, SigName,  // 2010-06-09 alf
                    x1 + (cos(rad) * x2),
                    y1 + (sin(rad) * x2 * EllipsFactor) );
          }
        else {
          sprintf(h, "%s %s (R%.9f %.9f);\n", PadVia, SigName,
                    x1 + (cos(rad) * x2),
                    y1 + (sin(rad) * x2 * EllipsFactor) );
          }
        s += h;
        SigName = "";
      }
    }
    else {
      for (real a = StartAngle; a < EndAngle; a += AngleStep) {
        rad = PI / 180 * a;
        if (PadVia == "PAD") sprintf(Rotate_option, "R%.2f", a);
        if (EAGLE_VERSION >= 4 && EAGLE_RELEASE >= 10 || EAGLE_VERSION >= 5) {
          sprintf(h, "%s %s %s (R%.9f %.9f);\n",  // 2010-06-09
                      PadVia,
                      Rotate_option,
                      SigName,
                      x1 + (cos(rad) * x2),
                      y1 + (sin(rad) * x2 * EllipsFactor) );
          }
        else {
          sprintf(h, "%s '%s' (R%.9f %.9f);\n",
                      PadVia,
                      SigName,
                      x1 + (cos(rad) * x2),
                      y1 + (sin(rad) * x2 * EllipsFactor) );
          }
        s += h;
        SigName = "";
      }
    }
  }
  else {
    if (PadVia == "PAD") sprintf(Rotate_option, "R%.2f", StartAngle);
        if (EAGLE_VERSION >= 4 && EAGLE_RELEASE >= 10 || EAGLE_VERSION >= 5) {
      sprintf(h, "%s %s %s (R%.9f %.9f);\n",  // 2010-06-09
                  PadVia,
                  Rotate_option,
                  SigName,
                  x1 + (cos(rad) * x2),
                  y1 + (sin(rad) * x2 * EllipsFactor) );
      s+= h;
    }
    else {
      sprintf(h, "%s '%s' (R%.9f %.9f);\n", // Via
                  PadVia,
                  SigName,
                  x1 + (cos(rad) * x2),
                  y1 + (sin(rad) * x2 * EllipsFactor) );
      s += h;
    }
  }
  return ;
}

// *** generate Script to place HOLEs ***
void drawHole(void) {
  real rad = PI / 180 * StartAngle;

  sprintf(h, "HOLE %s ", Drill_Hole);
  s += h;
  if (Placeform == ELLIPSE_4) {
    s += wireEllipse() + ";\n";;
  }
  else if (AngleStep) {
    if (AngleStep < 0) {
      if (StartAngle < EndAngle) StartAngle+= 360;
      for (real a = StartAngle; a > EndAngle; a += AngleStep) {
        rad = PI / 180 * a;
        sprintf(h, " (R%.9f %.9f)\n", x1 + (cos(rad) * x2), y1 + (sin(rad) * x2 * EllipsFactor) ); // 2013-08-05 no semicolon
        s += h;
      }
      s += ";\n";
    }
    else {
      for (real a = StartAngle; a < EndAngle; a += AngleStep) {
        rad = PI / 180 * a;
        sprintf(h, " (R%.9f %.9f)\n", x1 + (cos(rad) * x2), y1 + (sin(rad) * x2 * EllipsFactor) ); // 2013-08-05 no semicolon
        s += h;
      }
      s += ";\n";
    }
  }
  else {
    sprintf(h, "HOLE %s (R%.9f %.9f);\n", Drill_Hole,
                x1 + (cos(rad) * x2),
                y1 + (sin(rad) * x2 * EllipsFactor) );
    s += h;
  }
  return ;
}


void drawGroup(void) {
  real groupdistance, m;
  if (board) board(B) {
    gridunit = (B.grid.unit);
    m = abs(B.area.x2);
    if (groupdistance < m) groupdistance = m;
    m = abs(B.area.x1);
    if (groupdistance < m) groupdistance = m;
    m = abs(B.area.y2);
    if (groupdistance < m) groupdistance = m;
    m = abs(B.area.y1);
    if (groupdistance < m) groupdistance = m;
  }
  if (library) library(L) {
    gridunit = (L.grid.unit);
    if (package) package(P) {
      m = abs(P.area.x2);
      if (groupdistance < m) groupdistance = m;
      m = abs(P.area.x1);
      if (groupdistance < m) groupdistance = m;
      m = abs(P.area.y2);
      if (groupdistance < m) groupdistance = m;
      m = abs(P.area.y1);
      if (groupdistance < m) groupdistance = m;
    }
  }
  groupdistance = maxx;  // maximum
  if (!UseMarkedGroup) {  // 2011-10-21
    sprintf(s, "GROUP (%.9f %.9f) (%.9f %.9f) (%.9f %.9f) (%.9f %.9f) (>%.9f %.9f);\n",
              -groupdistance, -groupdistance,
               groupdistance, -groupdistance,
               groupdistance,  groupdistance,
              -groupdistance,  groupdistance,
              -groupdistance, -groupdistance
           );
  }
  sprintf(h, "CUT (R0 0);\n");
  s += h;
  for (real a = StartAngle; a <= EndAngle-AngleStep; a += AngleStep) {
    sprintf(h, "PASTE R%.2f (R0 0);\n", a);  // 2011-10-21
    s += h;
  }
  return;
}

void unknown(string m) {
  if (dlgMessageBox("unknown parameter\n" + m, "OK", "Cancel" ) != 0) exit(-1);
  return;
}


// ******* Main ***************************************************************
int n = 1;
if (argc > 1) {
  do {
    Para = strupr(argv[n]);
    // *** Order of parameters can changed here ***
    // *** Eagle-Parser cut character ' from argument ***
    if      (Para[0] == '+' )  { Para[0] = ' ';  x2           = strtod(Para); }
    else if (Para[0] == 'A' )  { Para[0] = ' ';  StartAngle   = strtod(Para); }
    else if (Para[0] == 'N' )  { Para[0] = ' ';  AngleStep    = strtod(Para); }
    else if (Para[0] == 'E' )  { Para[0] = ' ';  EndAngle     = strtod(Para); }
    else if (Para[0] == 'L' )  { layer   = strsub(Para, 1); }
    else if (Para[0] == 'W' )  { Para[0] = ' ';  width        = Para; DrawType = DrawWIRE; }
    else if (Para[0] == 'X' )  { Para[0] = ' ';  x1           = strtod(Para); }
    else if (Para[0] == 'Y' )  { Para[0] = ' ';  y1           = strtod(Para); }
    else if (Para[0] == 'O' )  {                 DrawType     = DrawPOLYGON;  }
    else if (Para[0] == 'P' )  {                 PadVia       = "PAD"; DrawType = DrawPAD;  }
    else if (Para[0] == 'V' )  {                 PadVia       = "VIA"; DrawType = DrawPAD;  }
    else if (Para[0] == 'S' )  {                 DrawType     = DrawSMD;      }
    else if (Para[0] == 'I' )  { Para[0] = ' ';  SMD_dx       = strtod(Para); }
    else if (Para[0] == 'T' )  { Para[0] = ' ';  SMD_dy       = strtod(Para); }
    else if (Para[0] == '-' )  { SigName = strsub(Para, 1); }
    else if (Para[0] == 'K' )  { Sides = strtol(strsub(Para, 1)); }   // number of polygon sides
    else if (Para[0] == 'B' )  {                                      // align polygon: BH = flat side horizontal, BV = vertical
                                 if      (Para[1] == 'H') Align = 1;
                                 else if (Para[1] == 'V') Align = 2;
                                 else unknown(Para);
                               }
    else if (Para[0] == 'D' )  { Para[0] = ' ';  PAD_diameter = Para;         }  // Pad/Via diameter
    else if (Para[0] == 'R' )  { Para[0] = ' ';  Drill_Hole   = Para;  DrawType = DrawHOLE; }
    else if (Para[0] == 0xb0 || Para[0] == '#' || strstr(Para, "°") == 0) { AngleStepTyp = Degreestep; }  // ° (Latin-1 / UTF-8) or #
    else if (Para[0] == '/' || Para[0] == '.') { AngleStepTyp = Calcstep; }  // / or .
    else if (Para[0] == 'G' )  {                 DrawType     = DrawGROUP;    }
    else if (strstr(Para, "MOVE") == 0) {        DrawType     = DrawMOVE;     }  // ** do not change order with next line **
    else if (Para[0] == 'M' )  {                 RotateMatch  = 1;            }  // ** do not change order with prior line **
    else if (Para[0] == 'C' )  {                 Placeform    = CIRCLE;       }
    else if (Para[0] == '0' )  { Para[0] = ' ';  Placeform    = FULL_ELLIPSE; }
    else if (Para[0] == 'F' )  { Para[0] = ' ';  EllipsFactor = strtod(Para); }
    else if (Para[0] == '4' )  {                 Placeform    = ELLIPSE_4;    }
    else unknown(Para);
    n++;
  } while (argv[n]);
}
else {
  if (board) {
    board(B) grid = B.grid.unit;
  }
  if (schematic) { schematic(S) grid = S.grid.unit; }
  if (library)   {
    if (package || symbol) {
      library(L)   grid = L.grid.unit;
    }
    else {
      dlgMessageBox("!Start this ULP in a Package or Symbol Editor", "OK");
      exit(0);
    }
  }
  Set_MinMax_Unit(grid);
  loadLayers();

  int Result;
  do {
    Result = menue();
    if (PressOk) {
      syncLayer();
      int validationErrors = error();
      if (validationErrors > 0) {
        string validationTitle;
        sprintf(validationTitle, "Input validation failed (%d issue(s))", validationErrors);
        dlgMessageBox(validationTitle + "\n\n" + ValidationMessage, "OK");
        PressOk = 0;
      }
    }
  } while(!PressOk);
}

SigName = strupr(SigName);
if (argc <= 1 && DrawType == DrawPOLYGON) SigName = "";   // dialog: no signal for polygons

sprintf(s, "SET Wire_Bend 2;\n");   // *** Script header ***
if (layer)        s += "CHANGE LAYER " + layer + ";\n";
if (PAD_diameter) s += "CHANGE DIAMETER " + PAD_diameter + ";\n";
if (Drill_Hole)   s += "CHANGE DRILL " + Drill_Hole + ";\n";
//if (SigName &&  DrawType == DrawSMD || DrawType == DrawSMD) s += "SMD " + SigName + ";\n"; // 2008.05.05

// Command line only: B (align) is meaningful only for a polygon with sides
if (argc > 1 && Align && !(DrawType == DrawPOLYGON && Sides > 0)) {
  dlgMessageBox("!Align (B) needs a polygon (O) with sides (K)", "OK");
  exit(-2);
}

// Polygon by number of sides: full 360 deg, step = 360 / Sides, Angle start = first vertex
if (DrawType == DrawPOLYGON && Sides > 0) {
  if (Sides < 3 || Placeform == ELLIPSE_4) {
    dlgMessageBox("!Sides: at least 3, and not usable with 1/4 ellipse", "OK");
    exit(-2);
  }
  AngleStepTyp = Degreestep;
  AngleStep    = 360.0 / Sides;
  if (Align) {   // flat side parallel to the screen: horizontal (on top) or vertical (on the right)
    if (Align == 1) StartAngle = 90.0 - AngleStep / 2;   // vertices at 90 deg +/- step/2
    else            StartAngle = AngleStep / 2;          // vertices at  0 deg +/- step/2
    while (StartAngle >= AngleStep) StartAngle -= AngleStep;   // keep it inside one step
    while (StartAngle < 0)          StartAngle += AngleStep;
  }
  EndAngle     = StartAngle + 360.0 - AngleStep / 2;   // exactly "Sides" vertices, immune to float rounding
}

// Validate command-line parameters as well as dialog input. Keep this before
// converting calculated step counts into angular increments.
if (argc > 1) {
  int validationErrors = error();
  if (validationErrors > 0) {
    string validationTitle;
    sprintf(validationTitle, "Input validation failed (%d issue(s))", validationErrors);
    dlgMessageBox(validationTitle + "\n\n" + ValidationMessage, "OK");
    exit(-2);
  }
}

if (Placeform == ELLIPSE_4) {
  if (EndAngle > 90.0) EndAngle = 90.0;
  if (StartAngle > EndAngle) StartAngle = 0.0;
}

if (AngleStepTyp == Calcstep && AngleStep == 0) {
  dlgMessageBox("!Missing parameter: number of steps", "OK");
  exit(-2);
}

switch(AngleStepTyp) {
    case None         : if (DrawType != DrawPOLYGON) {
                         AngleStep = 360;
                        }
                        break;
    case Degreestep   : if (!AngleStep) AngleStepTyp = None;
                        break;
    case Calcstep     : AngleStep = (EndAngle - StartAngle) / AngleStep;
                        break;
}

// the vertex loops (polygon, wire with steps) need a positive step: otherwise they never end and EAGLE hangs
if (DrawType == DrawPOLYGON || (DrawType == DrawWIRE && AngleStepTyp)) {
  if (AngleStep <= 0) {
    dlgMessageBox("!Angle step must be positive.\nCheck Angle step, Angle start and Angle end.", "OK");
    exit(-2);
  }
  if ((EndAngle - StartAngle) / AngleStep > 20000) {
    dlgMessageBox("!Too many vertices (more than 20000): increase the Angle step.", "OK");
    exit(-2);
  }
}

switch(DrawType) {
  case DrawWIRE    :  drawWire();
                      break;
  case DrawPOLYGON :  drawPolygon();
                      break;
  case DrawMOVE    :  drawMove();
                      break;
  case DrawGROUP   :  drawGroup();
                      break;
  case DrawHOLE    :  drawHole();
                      break;
  case DrawPAD     :  drawPad();
                      break;
  case DrawSMD     :  drawSmd();
                      break;
}


if (test) dlgDialog("Test") {
    dlgHBoxLayout dlgSpacing(500);
    dlgHBoxLayout {
      dlgVBoxLayout dlgSpacing(500);
      dlgTextView(s);
    }
    dlgHBoxLayout {
      dlgPushButton("OK") dlgAccept();
      dlgPushButton("ESC") { dlgReject(); exit(-1); }
      dlgStretch(1);
      dlgLabel(Version);
    }
  };

// Fit the drawing to the editor window after all generated commands have run.
s += "WINDOW FIT;\n";

exit (s);
